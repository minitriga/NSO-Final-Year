module deploy-site {
  namespace "http://com/example/deploysite";
  prefix deploy-site;

  import ietf-inet-types {
    prefix inet;
  }

  import tailf-common {
    prefix tailf;
  }

  import tailf-ncs {
    prefix ncs;
  }

augment /ncs:services { 

list deploy-site {
    description "Deploy Site";
    tailf:info "Deploy Site";
    key name;

    uses ncs:service-data;
    ncs:servicepoint "deploy-site";

    leaf name {
      tailf:info "Unique service id";
      tailf:cli-allow-range;
      type string;
    }

    leaf cust-id {
        mandatory true;
        tailf:info "Customer ID";
        type uint16 {
            range "1..4096";
        }
    }

    leaf vlan {
            mandatory true;
            type uint16 {
                range "1..4096";
            }
    }

    leaf bfd {
            tailf:info "Enable BFD";
            mandatory true;
            type boolean;
    }

    leaf ipv6 {
            tailf:info "Enable IPv6";
            mandatory true;
            type boolean;
    }

    leaf soo {
            tailf:info "Enable BGP Signle Site of Origin";
            mandatory true;
            type boolean;
    }

    list pe {
        key "id";

        leaf id {
          tailf:info "PE identifier";
          mandatory true;
          type string;
        }

        leaf device {
          mandatory true;
          type leafref {
            path "/ncs:devices/ncs:device/ncs:name";
          }
        }

        leaf loopback {
            tailf:info "IPv4 loopback address";
            mandatory true;
            type inet:ipv4-address;
            description "IPv4 loopback address";
        }

        leaf interface-type {
            tailf:info "Interface Type";
            description "Outbound Interface";
            mandatory true;
            type enumeration {
            enum "GigabitEthernet";
            }
        }

        leaf interface-number {
            tailf:info "Interface Number (e.g 1 | 0/1)";
            mandatory true;
            type string;
        }

        leaf ipv4-address {
            tailf:info "IPv4 Address of outbound interface";
            mandatory true;
            type inet:ipv4-address;
            description "IPv4 Address of outbound interface";
        }

        leaf ipv4-mask {
            tailf:info "IPv4 Mask of outbound interface";
            mandatory true;
            type inet:ipv4-address;
            description "IPv4 Mask of outbound interface";
        }

        leaf ipv6-address {
            tailf:info "IPv6 Address of outbound interface";
            mandatory true;
            type string;
            description "IPv6 Address of outbound interface";
        }

        leaf ngbr-address {
            tailf:info "IPv4 Neighbor Address";
            mandatory true;
            type inet:ipv4-address;
            description "IPv4 Neighbor Address";
        }

        leaf ngbr6-address {
            tailf:info "IPv6 Neighbor Address";
            mandatory true;
            type inet:ipv6-address;
            description "IPv6 Neighbor Address";
        }

        leaf as-number {
           tailf:info "CPE Router as-number";
           mandatory true;
           type string;
        }
        
        leaf remote-as-number {
           tailf:info "CPE Router as-number";
           mandatory true;
           type string;
        }
    }

    list cpe {
        key "id";

        leaf id {
          tailf:info "PE identifier";
          mandatory true;
          type string;
        }

        leaf device {
          mandatory true;
          type leafref {
            path "/ncs:devices/ncs:device/ncs:name";
          }
        }
        
        leaf interface-type {
            tailf:info "Interface Type";
            description "Outbound Interface";
            mandatory true;
            type enumeration {
            enum "GigabitEthernet";
            enum "ge";
            }
        }

        leaf interface-number {
            tailf:info "Interface Number (e.g 1 | 0/1)";
            mandatory true;
            type string;
        }

        leaf ipv4-address {
            tailf:info "IPv4 Address of outbound interface";
            mandatory true;
            type inet:ipv4-address;
            description "IPv4 Address of outbound interface";
        }

        leaf ipv4-mask {
            tailf:info "IPv4 Mask of outbound interface";
            mandatory true;
            type inet:ipv4-address;
            description "IPv4 Mask of outbound interface";
        }

        leaf ipv4-prefix {
            tailf:info "IPv4 Prefix of outbound interface (e.g /30)";
            type string;
            description "IPv4 Mask of outbound interface (e.g /30)";
        }

        leaf ipv6-address {
            tailf:info "IPv6 Address of outbound interface";
            mandatory true;
            type string;
            description "IPv6 Address of outbound interface";
        }

        leaf ngbr-address {
            tailf:info "IPv4 Neighbor Address";
            mandatory true;
            type inet:ipv4-address;
            description "IPv4 Neighbor Address";
        }

        leaf ngbr6-address {
            tailf:info "IPv6 Neighbor Address";
            mandatory true;
            type inet:ipv6-address;
            description "IPv6 Neighbor Address";
        }

        leaf as-number {
           tailf:info "CPE Router as-number";
           mandatory true;
           type string;
        }
        
        leaf remote-as-number {
           tailf:info "CPE Router as-number";
           mandatory true;
           type string;
        }
    } 
  }
  }
}
